"""Parametric MG996R fit prototype inspired by micromet / Thingiverse 1941574.
Servo dimensions and horn interfaces still require physical confirmation.
Run through FreeCAD MCP. Does not overwrite existing CAD.
"""
import os
import json
import math
import FreeCAD as App
import FreeCADGui as Gui
import Part
import MeshPart

ROOT = os.path.dirname(os.path.dirname(os.path.dirname(os.path.abspath(__file__))))
OUT = os.path.join(ROOT, 'experiments/pan-tilt-mg996r')
if os.path.exists(os.path.join(OUT, 'assembly.FCStd')):
    raise RuntimeError('Refusing to overwrite existing prototype')
V = App.Vector
P = dict(body_length=40.7, body_width=20.0, body_height=36.6,
         flange_length=53.6, flange_bottom=26.6, flange_thickness=2.5,
         shaft_top=42.9, shaft_offset=-10.15, hole_pitch_x=48.2,
         hole_pitch_y=10.0, fit_clearance=0.5, mount_slot_length=7.0,
         mount_slot_width=3.4, pan_horn_plane=10.0,
         tilt_axis_x=-33.0, tilt_axis_z=95.0, tilt_servo_back_y=19.5,
         side_inner_y=26.0, side_thickness=3.0,
         platform_under_z=113.0, platform_thickness=3.5,
         pan_horn_bolt_circle=15.6, pan_horn_diameter=21.4,
         tilt_horn_bolts=(11.0,17.5))
docs = {}
shapes = {}

def box(x,y,z,dx,dy,dz):
    return Part.makeBox(dx,dy,dz,V(x,y,z))

def cyl(r,h,p,axis=(0,0,1)):
    return Part.makeCylinder(r,h,V(*p),V(*axis))

def combine(seq):
    return seq[0].multiFuse(seq[1:]).removeSplitter() if len(seq)>1 else seq[0]

def subtract(shape, tools):
    return shape.cut(combine(tools)).removeSplitter()

def slot_x(x,y,z,length,width,depth,axis='z'):
    half=(length-width)/2
    if axis=='z':
        return combine([cyl(width/2,depth,(x-half,y,z)),cyl(width/2,depth,(x+half,y,z)),box(x-half,y-width/2,z,2*half,width,depth)])
    return combine([cyl(width/2,depth,(x-half,y,z),(0,1,0)),cyl(width/2,depth,(x+half,y,z),(0,1,0)),box(x-half,y,z-width/2,2*half,depth,width)])

def prism_xz(points,y,thickness):
    vs=[V(x,y,z) for x,z in points]
    return Part.Face(Part.makePolygon(vs+[vs[0]])).extrude(V(0,thickness,0))

def save_part(name,shape,color):
    if not shape.isValid() or len(shape.Solids)!=1:
        raise RuntimeError('Invalid/disconnected '+name)
    d=App.newDocument('MG996R_'+name)
    table=d.addObject('Spreadsheet::Sheet','Dimensions')
    for i,(k,v) in enumerate(P.items(),1):
        table.set('A'+str(i),k);table.set('B'+str(i),str(v))
    o=d.addObject('PartDesign::Feature','Result')
    o.Label=name
    o.Shape=shape
    o.addProperty('App::PropertyString','Status').Status='Parametric macro prototype; actual servo/horns need measurement'
    o.ViewObject.ShapeColor=color
    d.recompute();d.saveAs(os.path.join(OUT,name+'.FCStd'))
    Part.export([o],os.path.join(OUT,name+'.step'))
    if name!='servo-envelope':
        mesh=MeshPart.meshFromShape(Shape=shape,LinearDeflection=0.12,AngularDeflection=0.25,Relative=False)
        mesh.write(os.path.join(OUT,name+'.stl'))
    docs[name]=d;shapes[name]=shape
    return o

# Servo envelope, dimensions from the archived drawing; holes and shaft offset nominal.
L=P['body_length'];W=P['body_width'];F=P['flange_bottom'];FT=P['flange_thickness']
servo=combine([box(-L/2,-W/2,0,L,W,P['body_height']),
               box(-P['flange_length']/2,-W/2,F,P['flange_length'],W,FT),
               cyl(6,3.0,(P['shaft_offset'],0,36.6)),
               cyl(3,6.3,(P['shaft_offset'],0,36.6))])
servo=subtract(servo,[cyl(2.1,FT+2,(x,y,F-1)) for x in [-24.1,24.1] for y in [-5,5]])
save_part('servo-envelope',servo,(0.16,0.18,0.21))

# Lower output points down. Its flange underside lands on the carrier top.
pan_rot=App.Rotation(V(1,0,0),180)
pan_pos=V(10.15,0,P['pan_horn_plane']+P['shaft_top'])
pan_place=App.Placement(pan_pos,pan_rot)
pan_floor=pan_pos.z-F-FT-4
cx=pan_pos.x

# Rounded rectangular base and circular horn seat: retained from the reference layout.
base=combine([box(-36.5,-27.5,0,73,55,4),box(-42.5,-21.5,0,85,43,4)]+[cyl(6,4,(x,y,0)) for x in [-36.5,36.5] for y in [-21.5,21.5]]+[cyl(18.2,12,(0,0,0))])
cuts=[cyl(4.5,14,(0,0,-1)),cyl(P['pan_horn_diameter']/2,5,(0,0,8))]
for x,y in [(-36.5,-21.5),(-36.5,21.5),(36.5,-21.5),(36.5,21.5)]:cuts.append(cyl(2,6,(x,y,-1)))
for x,y in [(7.8,0),(-7.8,0),(0,7.8),(0,-7.8)]:cuts.append(cyl(1.2,14,(x,y,1)))
base=subtract(base,cuts)
save_part('base',base,(0.85,0.84,0.75))

# Carrier and bearing cup. Slot ends cover approximately 47..51 mm ear pitches.
plate=box(cx-34,-26,pan_floor,68,52,4)
cup=subtract(cyl(21,pan_floor+4-5,(0,0,5)),[cyl(18.7,pan_floor+5-5,(0,0,4.5))])
carrier=combine([plate,cup])
cuts=[box(cx-L/2-0.5,-10.5,pan_floor-1,L+1,21,6),cyl(7,40,(0,0,0))]
for x in [cx-24.1,cx+24.1]:
    for y in [-5,5]:cuts.append(slot_x(x,y,pan_floor-1,7,3.4,6))
for x in [cx-18,cx+18]:cuts.append(cyl(1.7,60,(x,-30,pan_floor+2),(0,1,0)))
carrier=subtract(carrier,cuts)
save_part('pan-carrier',carrier,(0.28,0.31,0.35))

# Both side plates retain the triangular profile and through-hole aesthetic.
ax=P['tilt_axis_x'];az=P['tilt_axis_z'];bottom=pan_floor-3
profile=[(ax-7.5,az),(ax-7.5,bottom),(cx+34,bottom),(cx+34,bottom+12),(ax+8,az+7.5),(ax,az+7.5)]
for name,y,drive in [('servo-side',-29,True),('shaft-side',26,False)]:
    side=combine([prism_xz(profile,y,3),cyl(7.5,3,(ax,y,az),(0,1,0))])
    cuts=[cyl(10,5,(-1,y-1,52),(0,1,0))]
    for x in [cx-18,cx+18]:cuts.append(cyl(1.7,5,(x,y-1,pan_floor+2),(0,1,0)))
    if drive:
        cuts.append(cyl(4.5,5,(ax,y-1,az),(0,1,0)))
        for dx in P['tilt_horn_bolts']:cuts.append(cyl(1.2,5,(ax+dx,y-1,az),(0,1,0)))
    side=subtract(side,cuts)
    if not drive:
        side=combine([side,cyl(3,6,(ax,20,az),(0,1,0))])
    save_part(name,side,(0.85,0.84,0.75))

# Upper servo lies across Y. Its shaft points toward the negative-Y side plate.
tilt_rot=App.Rotation(V(1,0,0),90)
tilt_pos=V(ax-P['shaft_offset'],P['tilt_servo_back_y'],az)
tilt_place=App.Placement(tilt_pos,tilt_rot)
platform=box(-56,-29,113,72,58,3.5)
mount_face=tilt_pos.y-F-FT
mount_x=[tilt_pos.x-24.1,tilt_pos.x+24.1]
for x in mount_x:
    platform=combine([platform,box(x-5.8,mount_face-7,az-8,11.6,7,113-(az-8)+0.5)])
# Opposite support: 0.5 mm behind servo back face, bore coaxial with its shaft.
platform=combine([platform,box(ax-7,20,az,14,6,113-az+0.5),cyl(7,6,(ax,20,az),(0,1,0))])
cuts=[cyl(16,7,(-18,-1,111)),cyl(3.25,8,(ax,19,az),(0,1,0))]
for x in mount_x:
    for z in [az-5,az+5]:cuts.append(slot_x(x,mount_face-8,z,7,3.4,10,'y'))
for x in [-49,9]:
    for y in [-22,22]:cuts.append(cyl(1.7,7,(x,y,111)))
platform=subtract(platform,cuts)
save_part('tilt-platform',platform,(0.28,0.31,0.35))

doc=App.newDocument('PanTiltMG996R')
doc.saveAs(os.path.join(OUT,'assembly.FCStd'))
pan=doc.addObject('App::Part','Pan')
pan.addProperty('App::PropertyAngle','Yaw','Motion').Yaw=0
tilt=doc.addObject('App::Part','Tilt')
tilt.addProperty('App::PropertyAngle','Pitch','Motion').Pitch=0
pan.addObject(tilt)
for name in ['base','pan-carrier','servo-side','shaft-side','tilt-platform','servo-envelope']:
    if name=='servo-envelope':continue
    link=doc.addObject('App::Link',name.replace('-','_'))
    link.setLink(docs[name].getObject('Result'));link.LinkTransform=True
    if name=='tilt-platform':tilt.addObject(link)
    elif name!='base':pan.addObject(link)
for name,placement,group in [('PanServo',pan_place,pan),('TiltServo',tilt_place,tilt)]:
    link=doc.addObject('App::Link',name);link.setLink(docs['servo-envelope'].getObject('Result'))
    link.LinkTransform=True;link.Placement=placement;group.addObject(link)

# Check static contacts and envelope intersections at sampled pitch angles.
def moved(shape,placement):
    s=shape.copy();s.Placement=placement.multiply(s.Placement);return s

ps=moved(servo,pan_place);ts=moved(servo,tilt_place)
report={'parameters':P,'nominal_only':['servo mounting pitch','shaft offset','horn dimensions'],
        'static_intersections_mm3':{},'motion':[]}
for n,a,b in [('pan-servo/carrier',ps,carrier),('tilt-servo/platform',ts,platform),('base/carrier',base,carrier)]:
    report['static_intersections_mm3'][n]=round(a.common(b).Volume,5)
for pitch in range(-30,31,10):
    rot=App.Rotation(V(0,1,0),pitch)
    pivot=V(ax,0,az)
    t=App.Placement(pivot-rot.multVec(pivot),rot)
    mp=moved(platform,t);ms=moved(ts,t)
    overlaps={}
    for fixed in ['pan-carrier','servo-side','shaft-side']:
        overlaps[fixed]=round(mp.common(shapes[fixed]).Volume+ms.common(shapes[fixed]).Volume,5)
    overlaps['pan-servo']=round(mp.common(ps).Volume+ms.common(ps).Volume,5)
    report['motion'].append({'pitch':pitch,'overlap_mm3':overlaps})
report['passed']=all(v<0.01 for v in report['static_intersections_mm3'].values()) and all(v<0.01 for row in report['motion'] for v in row['overlap_mm3'].values())
with open(os.path.join(OUT,'verification.json'),'w') as f:json.dump(report,f,indent=2)
doc.recompute();doc.save()
App.setActiveDocument(doc.Name)
Gui.Selection.clearSelection()
Gui.activeDocument().activeView().viewAxonometric();Gui.activeDocument().activeView().fitAll()
Gui.activeDocument().activeView().saveImage(os.path.join(OUT,'assembly.png'),1400,1100,'White')
print(json.dumps(report))
