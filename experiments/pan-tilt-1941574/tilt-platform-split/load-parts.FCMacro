"""Load four SCAD partitions without moving any existing assembly object."""
import os
import Mesh
import FreeCAD as App
import FreeCADGui as Gui

OUT=os.path.dirname(os.path.abspath(__file__))
assembly=App.getDocument('PanTiltOriginalWithUserMG996R')
if assembly.getObject('TiltPlatformParts') is not None:
    raise RuntimeError('Split group already exists')
group=assembly.addObject('App::DocumentObjectGroup','TiltPlatformParts')
group.Label='TiltPlatform — четыре части'
original=assembly.getObject('TiltPlatform')
placement=App.Placement(original.Placement)
items=[('platform-plate','PlatformPlate','Площадка',(0.25,0.3,0.35)),
       ('servo-mount-tall','ServoMountTall','Высокое крепление серво',(0.85,0.5,0.2)),
       ('servo-mount-short','ServoMountShort','Низкое крепление серво',(0.25,0.65,0.85)),
       ('axle-support','AxleSupport','Опора оси',(0.45,0.75,0.35))]
for file,name,label,color in items:
    target=os.path.join(OUT,file+'.FCStd')
    if os.path.exists(target):raise RuntimeError('Refusing to overwrite '+target)
    doc=App.newDocument('Split_'+name)
    obj=doc.addObject('Mesh::Feature','Part')
    obj.Label=label;obj.Mesh=Mesh.Mesh(os.path.join(OUT,file+'.stl'))
    obj.ViewObject.ShapeColor=color
    obj.addProperty('App::PropertyString','Source').Source='micromet Thingiverse 1941574; original SCAD partition, CC BY-SA'
    doc.recompute();doc.saveAs(target)
    link=assembly.addObject('App::Link',name)
    link.setLink(obj);link.LinkTransform=True;link.Placement=placement
    group.addObject(link)
original.Visibility=False
assembly.recompute();assembly.save()
App.setActiveDocument(assembly.Name)
Gui.Selection.clearSelection()
print('Four separate parts added at original placement. Original TiltPlatform retained hidden; all original placements unchanged.')
