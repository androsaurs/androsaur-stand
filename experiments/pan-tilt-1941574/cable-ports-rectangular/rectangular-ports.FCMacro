"""Replace circular cable exits with vertical rounded rectangles, centers unchanged."""
import os
import json
import FreeCAD as App
import FreeCADGui as Gui
import Part
import MeshPart

OUT=os.path.dirname(os.path.abspath(__file__))
native=App.getDocument('HollowBase')
assembly=App.getDocument('PanTiltOriginalWithUserMG996R')
if native.getObject('RectangularPortDimensions') is not None:
    raise RuntimeError('Rectangular ports already exist')
sizes=native.addObject('App::FeaturePython','RectangularPortDimensions')
for name,value in [('ChargingWidth',12),('ChargingHeight',18),('MotorWidth',10),
                   ('MotorHeight',16),('CornerRadius',2),('CutDepth',22.2)]:
    sizes.addProperty('App::PropertyLength',name,'Dimensions');setattr(sizes,name,value)

def rounded_tool(prefix,width_name,height_name,old):
    # Original tool local X maps to vertical Z; local Y maps to facade width.
    w='RectangularPortDimensions.'+width_name
    h='RectangularPortDimensions.'+height_name
    r='RectangularPortDimensions.CornerRadius'
    depth='RectangularPortDimensions.CutDepth'
    primitives=[]
    for suffix,length,width,x,y in [
        ('CoreA',h+' - 2 * '+r,w,'-'+h+'/2 + '+r,'-'+w+'/2'),
        ('CoreB',h,w+' - 2 * '+r,'-'+h+'/2','-'+w+'/2 + '+r),
    ]:
        obj=native.addObject('Part::Box',prefix+suffix)
        for prop,expr in [('Length',length),('Width',width),('Height',depth),
                          ('Placement.Base.x',x),('Placement.Base.y',y)]:
            obj.setExpression(prop,expr)
        primitives.append(obj)
    for i,(sx,sy) in enumerate([(-1,-1),(-1,1),(1,-1),(1,1)],1):
        obj=native.addObject('Part::Cylinder',prefix+'Corner'+str(i))
        obj.setExpression('Radius',r);obj.setExpression('Height',depth)
        obj.setExpression('Placement.Base.x',str(sx)+' * ('+h+'/2 - '+r+')')
        obj.setExpression('Placement.Base.y',str(sy)+' * ('+w+'/2 - '+r+')')
        primitives.append(obj)
    fused=native.addObject('Part::MultiFuse',prefix)
    fused.Shapes=primitives;fused.Refine=True
    fused.Placement=App.Placement(old.Placement)
    for obj in primitives:obj.Visibility=False
    old.Visibility=False
    return fused

old_charge=native.getObject('ChargingCablePort')
old_motor=native.getObject('MotorCablePort')
charge=rounded_tool('ChargingRectangle','ChargingWidth','ChargingHeight',old_charge)
motor=rounded_tool('MotorRectangle','MotorWidth','MotorHeight',old_motor)
result=native.getObject('Base');before=result.Shape.copy()
native.getObject('CableOpenings').Shapes=[native.getObject('CableCavity'),charge,motor]
native.recompute()
assert result.Shape.isValid() and len(result.Shape.Solids)==1
assert result.Shape.cut(before).Volume<1e-6
assert before.cut(result.Shape).Volume>0
for tool,old in [(charge,old_charge),(motor,old_motor)]:
    assert (tool.Placement.Base-old.Placement.Base).Length<1e-9
    tool.Visibility=False
native.getObject('CableOpenings').Visibility=False
result.Visibility=True
native.save()
base=assembly.getObject('Base');placement=App.Placement(base.Placement)
mesh=MeshPart.meshFromShape(Shape=result.Shape,LinearDeflection=0.05,AngularDeflection=0.15,Relative=False)
base.Mesh=mesh;base.Placement=placement
for name,value in [('ChargingPortWidth',12),('ChargingPortHeight',18),('MotorPortWidth',10),('MotorPortHeight',16),('PortCornerRadius',2)]:
    if name not in base.PropertiesList:base.addProperty('App::PropertyLength',name,'CablePorts')
    setattr(base,name,value)
for name in ['ChargingPortDiameter','MotorPortDiameter']:
    if name in base.PropertiesList:base.removeProperty(name)
assembly.recompute();assembly.save()
for folder in [OUT,os.path.dirname(native.FileName)]:
    Part.export([result],os.path.join(folder,'base-hollow.step'))
    mesh.write(os.path.join(folder,'base-hollow.stl'))
App.setActiveDocument(assembly.Name);Gui.Selection.clearSelection()
print(json.dumps({'charging_width_height_mm':[12,18],'motor_width_height_mm':[10,16],
                 'corner_radius_mm':2,'centers_preserved':True,'placements_unchanged':True,
                 'valid_single_solid':True}))
