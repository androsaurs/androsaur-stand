"""Simple slide-in phone cradle on the existing platform. No existing geometry edits."""
import os
import FreeCAD as App
import FreeCADGui as Gui
import Part
import MeshPart

OUT=os.path.dirname(os.path.abspath(__file__))
target=os.path.join(OUT,'phone-holder-170x80.FCStd')
if os.path.exists(target):raise RuntimeError('Refusing to overwrite phone holder')
assembly=App.getDocument('PanTiltOriginalWithUserMG996R')
platform=assembly.getObject('TiltPlatformReassembled')
side=assembly.getObject('ShaftSide')
V=App.Vector
pivot=side.Placement.multVec(V(-37.5,20.5,1.5))
center_x=platform.Placement.inverse().multVec(pivot).x
doc=App.newDocument('PhoneHolder170x80')
sheet=doc.addObject('Spreadsheet::Sheet','Dimensions')
values=[('PhoneHeight',170),('PhoneWidth',80),('PhoneThickness',10),
        ('FitClearance',0.3),('WallThickness',2),('BackThickness',3),
        ('AxisCenterX',center_x),('PlatformFaceZ',-1.5)]
for i,(name,value) in enumerate(values,1):
    sheet.set('A'+str(i),name);sheet.set('B'+str(i),'='+str(value)+' mm');sheet.setAlias('B'+str(i),name)

def box(name,expressions):
    obj=doc.addObject('Part::Box',name)
    for prop,expr in expressions.items():obj.setExpression(prop,expr)
    return obj

back=box('BackPlate',{
    'Length':'Dimensions.PhoneHeight + 2 * Dimensions.FitClearance + 2 * Dimensions.WallThickness',
    'Width':'Dimensions.PhoneWidth + 2 * Dimensions.FitClearance + 2 * Dimensions.WallThickness',
    'Height':'Dimensions.BackThickness',
    'Placement.Base.x':'Dimensions.AxisCenterX - Length / 2',
    'Placement.Base.y':'-Width / 2',
    'Placement.Base.z':'Dimensions.PlatformFaceZ - Dimensions.BackThickness'})
walls=[]
for name,positive in [('LeftRail',False),('RightRail',True)]:
    rail=box(name,{
        'Length':'BackPlate.Length','Width':'Dimensions.WallThickness',
        'Height':'Dimensions.PhoneThickness + 0.6 mm',
        'Placement.Base.x':'BackPlate.Placement.Base.x',
        'Placement.Base.y':('(Dimensions.PhoneWidth / 2 + Dimensions.FitClearance)' if positive else '-Dimensions.PhoneWidth / 2 - Dimensions.FitClearance - Dimensions.WallThickness'),
        'Placement.Base.z':'BackPlate.Placement.Base.z - Dimensions.PhoneThickness - 0.5 mm'})
    walls.append(rail)
stop=box('BottomStop',{
    'Length':'Dimensions.WallThickness','Width':'Dimensions.PhoneWidth + 2 * Dimensions.FitClearance',
    'Height':'Dimensions.PhoneThickness + 0.6 mm',
    'Placement.Base.x':'BackPlate.Placement.Base.x',
    'Placement.Base.y':'-Width / 2',
    'Placement.Base.z':'BackPlate.Placement.Base.z - Dimensions.PhoneThickness - 0.5 mm'})
blank=doc.addObject('Part::MultiFuse','HolderBlank');blank.Shapes=[back]+walls+[stop]
holes=[]
for i,(x,y) in enumerate([(-27,-21),(-27,17),(23,-21),(23,17)],1):
    hole=doc.addObject('Part::Cylinder','MountHole'+str(i))
    hole.Radius=1.7;hole.Height=5
    hole.Placement.Base=V(x,y,-5.5);holes.append(hole)
tools=doc.addObject('Part::MultiFuse','MountHoles');tools.Shapes=holes
holder=doc.addObject('Part::Cut','Holder');holder.Base=blank;holder.Tool=tools
holder.Label='Держатель телефона 170 × 80 мм'
holder.ViewObject.ShapeColor=(0.24,0.63,0.73)
holder.addProperty('App::PropertyString','Status').Status='Simple fit mockup; 10 mm thickness assumed. Open top; no front retaining catches.'
phone=box('PhoneEnvelope',{
    'Length':'Dimensions.PhoneHeight','Width':'Dimensions.PhoneWidth','Height':'Dimensions.PhoneThickness',
    'Placement.Base.x':'Dimensions.AxisCenterX - Dimensions.PhoneHeight / 2',
    'Placement.Base.y':'-Dimensions.PhoneWidth / 2',
    'Placement.Base.z':'BackPlate.Placement.Base.z - Dimensions.PhoneThickness'})
phone.Label='Телефон 170 × 80 × 10 мм — габарит'
phone.ViewObject.ShapeColor=(0.2,0.22,0.25);phone.ViewObject.Transparency=65
doc.recompute()
assert holder.Shape.isValid() and len(holder.Shape.Solids)==1
assert holder.Shape.common(phone.Shape).Volume<1e-6
for o in [back,blank,stop,tools]+walls+holes:o.Visibility=False
doc.saveAs(target)
Part.export([holder],os.path.join(OUT,'phone-holder-170x80.step'))
MeshPart.meshFromShape(Shape=holder.Shape,LinearDeflection=0.1,AngularDeflection=0.2,Relative=False).write(os.path.join(OUT,'phone-holder-170x80.stl'))

group=assembly.addObject('App::Part','PhoneMount')
group.Label='Телефон и держатель'
group.setExpression('Placement','TiltPlatformReassembled.Placement')
for name,source in [('PhoneHolder',holder),('PhoneEnvelope',phone)]:
    link=assembly.addObject('App::Link',name);link.setLink(source);link.LinkTransform=True
    group.addObject(link);link.Placement=App.Placement()
assembly.recompute();assembly.save()
App.setActiveDocument(assembly.Name)
Gui.Selection.clearSelection()
Gui.activeDocument().activeView().viewAxonometric();Gui.activeDocument().activeView().fitAll()
Gui.activeDocument().activeView().saveImage(os.path.join(OUT,'assembly-with-phone.png'),1400,1100,'White')
print('CREATED',target,'phone midpoint on tilt-axis height; existing objects unchanged')
