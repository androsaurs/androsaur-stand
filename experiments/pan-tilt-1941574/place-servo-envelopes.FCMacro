"""Place existing reference servo envelopes to communicate installation directions."""
import os
import FreeCAD as App
import FreeCADGui as Gui

ROOT = os.path.dirname(os.path.dirname(os.path.dirname(os.path.abspath(__file__))))
path = os.path.join(ROOT, 'experiments/pan-tilt-1941574/pan-tilt-1941574.FCStd')
doc = next((d for d in App.listDocuments().values() if d.FileName == path), None)
if doc is None:
    doc = App.openDocument(path)
source = os.path.join(ROOT, 'cad/components/servo-reference/servo-352944.FCStd')
sd = next((d for d in App.listDocuments().values() if d.FileName == source), None)
if sd is None:
    sd = App.openDocument(source)
servo = sd.getObject('Servo')
V = App.Vector

for name, carrier, local in [
    ('PanServoReference', 'PanCarrier', App.Placement(V(0, 0, -26.7), App.Rotation(V(0, 0, 1), 180))),
    ('TiltServoReference', 'TiltPlatform', App.Placement(V(-1.5, 26.7, 11.5), App.Rotation(V(1, 0, 0), 90))),
]:
    obj = doc.getObject(name)
    if obj is None:
        obj = doc.addObject('App::Link', name)
        obj.setLink(servo)
        obj.LinkTransform = True
        doc.getObject('OriginalParts').addObject(obj)
        obj.addProperty('App::PropertyString', 'Purpose')
    obj.Purpose = 'Installation direction only; unverified reference envelope, not exact MG996R mounting'
    obj.Placement = doc.getObject(carrier).Placement.multiply(local)
    obj.Visibility = True

doc.recompute()
doc.save()
App.setActiveDocument(doc.Name)
Gui.Selection.clearSelection()
Gui.activeDocument().activeView().viewAxonometric()
Gui.activeDocument().activeView().fitAll()
Gui.activeDocument().activeView().saveImage(os.path.join(ROOT, 'experiments/pan-tilt-1941574/assembly-with-servos.png'), 1400, 1100, 'White')
print('Placed both reference servos; original mesh placements unchanged')
