# BRep-детали держателя из двух деталей по STL владельца (references/phone-holder-two-piece).
# Сетки призматические: соседние компланарные грани склеиваются в плоские грани тела.
# Начало координат — минимум габарита сетки, как у прежних деталей, поэтому Placement в сборке прежний.
# Существующие файлы не перезаписываются.
import os
import Mesh
import Part
import FreeCAD as App
from FreeCAD import Vector as V

REPO = "/mnt/fastdata/hram/projects/androsaurs/androsaur-stand"

PARTS = {
    "phone-holder-body": ("Body — спинка держателя (BRep)", "Body.stl"),
    "phone-grip-82mm": ("82mm — поперечный захват (BRep)", "82mm.stl"),
}


def solid_from_stl(path):
    mesh = Mesh.Mesh(path)
    bb = mesh.BoundBox
    shape = Part.Shape()
    shape.makeShapeFromMesh(mesh.Topology, 0.001, True)
    shell = shape.Shells[0] if len(shape.Shells) == 1 else Part.Shell(shape.Faces)
    solid = Part.Solid(shell)
    if solid.Volume < 0:
        solid.reverse()
    solid = solid.removeSplitter()
    solid.translate(V(-bb.XMin, -bb.YMin, -bb.ZMin))
    return solid, mesh, (bb.XMin, bb.YMin, bb.ZMin)


def build_all(repo=REPO):
    made = {}
    for key, (label, stl) in PARTS.items():
        path = os.path.join(repo, "cad", "parts", key, key + ".FCStd")
        if os.path.exists(path):
            App.Console.PrintWarning("exists, skipped: %s\n" % path)
            continue
        solid, mesh, origin = solid_from_stl(os.path.join(repo, "references", "phone-holder-two-piece", stl))
        assert solid.isValid() and len(solid.Solids) == 1, key
        os.makedirs(os.path.dirname(path), exist_ok=True)
        doc = App.newDocument(key.replace("-", "_"))
        part = doc.addObject("Part::Feature", "Part")
        part.Label = label
        part.Shape = solid
        sheet = doc.addObject("Spreadsheet::Sheet", "Dimensions")
        rows = [("Источник", "references/phone-holder-two-piece/" + stl),
                ("Сдвиг начала координат, мм", "минимум габарита сетки в исходных координатах %.3f %.3f %.3f перенесён в 0" % origin),
                ("Объём сетки, мм3", "%.2f" % mesh.Volume), ("Объём BRep, мм3", "%.2f" % solid.Volume),
                ("Граней в BRep", str(len(solid.Faces))), ("Построение", "scripts/build-phone-holder-brep.FCMacro")]
        for i, (k, v) in enumerate(rows, 1):
            sheet.set("A%d" % i, k)
            sheet.set("B%d" % i, v)
        doc.recompute()
        doc.saveAs(path)
        made[key] = (path, round(solid.Volume, 2), len(solid.Faces))
    return made
