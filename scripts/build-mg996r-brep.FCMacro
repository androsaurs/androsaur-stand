# BRep-габарит MG996R по замерам пользовательской сетки components/mg996r/mg996r.FCStd.
# Система координат та же, что у сетки: X — ширина, Y — высота от низа, Z — длина.
# Ось вала вдоль Y через x = 9,5, z = 37,0. Существующий файл не перезаписывается.
import os
import Part
import FreeCAD as App
from FreeCAD import Vector as V

REPO = "/mnt/fastdata/hram/projects/androsaurs/androsaur-stand"
SHAFT_X, SHAFT_Z = 9.5, 37.0
EAR_Z0, EAR_Z1, EAR_Y0, EAR_Y1 = 0.0, 54.0, 26.5, 29.0
HOLE_D, HOLE_PITCH_Z, HOLE_PITCH_X = 4.0, 49.5, 10.0


def box(x0, x1, y0, y1, z0, z1):
    return Part.makeBox(x1 - x0, y1 - y0, z1 - z0, V(x0, y0, z0))


def cyl_y(r, y0, y1, x, z):
    return Part.makeCylinder(r, y1 - y0, V(x, y0, z), V(0, 1, 0))


def rect_wire(x0, x1, z0, z1, y):
    pts = [V(x0, y, z0), V(x1, y, z0), V(x1, y, z1), V(x0, y, z1), V(x0, y, z0)]
    return Part.makePolygon(pts)


def wedge(z_end, z_root):
    """Клин над концом ушей: от y = 29 у края до y = 30 у корпуса, по всей ширине x."""
    pts = [V(0, EAR_Y1, z_end), V(0, EAR_Y1, z_root), V(0, EAR_Y1 + 1.0, z_root), V(0, EAR_Y1, z_end)]
    face = Part.Face(Part.makePolygon(pts))
    return face.extrude(V(19.0, 0, 0))


def build():
    lower = Part.makeLoft([rect_wire(1.1, 17.9, 7.9, 46.1, 0.0), rect_wire(0.0, 19.0, 7.0, 47.0, 3.0)], True)
    body = lower.fuse(box(0, 19, 3.0, 35.0, 7.0, 47.0))
    ears = box(0, 19, EAR_Y0, EAR_Y1, EAR_Z0, EAR_Z1)
    cover = box(0, 19, 35.0, 37.25, 10.5, 46.5)
    pad = box(1, 18, 37.25, 37.5, 13.5, 43.5)
    boss = (cyl_y(6.5, 37.25, 38.5, SHAFT_X, SHAFT_Z)
            .fuse(cyl_y(5.5, 38.5, 39.5, SHAFT_X, SHAFT_Z))
            .fuse(cyl_y(2.5, 39.5, 40.5, SHAFT_X, SHAFT_Z))
            .fuse(cyl_y(2.8, 40.5, 43.5, SHAFT_X, SHAFT_Z)))
    cable = Part.makeCylinder(1.5, 7.5, V(9.5, 8.5, 47.0), V(0, 0, 1))
    shape = body
    for s in (ears, cover, pad, boss, cable, wedge(EAR_Z0, 7.0), wedge(EAR_Z1, 47.0)):
        shape = shape.fuse(s)
    ear_zc = (EAR_Z0 + EAR_Z1) / 2
    for sx in (-1, 1):
        for sz in (-1, 1):
            shape = shape.cut(cyl_y(HOLE_D / 2, EAR_Y0 - 1, EAR_Y1 + 1.5,
                                    SHAFT_X + sx * HOLE_PITCH_X / 2, ear_zc + sz * HOLE_PITCH_Z / 2))
    shape = shape.cut(cyl_y(1.5, 39.0, 44.0, SHAFT_X, SHAFT_Z))
    return shape.removeSplitter()


def build_doc(repo=REPO):
    key = "mg996r-brep"
    path = os.path.join(repo, "cad", "components", key, key + ".FCStd")
    if os.path.exists(path):
        App.Console.PrintWarning("exists, skipped: %s\n" % path)
        return None
    os.makedirs(os.path.dirname(path), exist_ok=True)
    shape = build()
    doc = App.newDocument("mg996r_brep")
    part = doc.addObject("Part::Feature", "Part")
    part.Label = "MG996R — BRep-габарит"
    part.Shape = shape
    sheet = doc.addObject("Spreadsheet::Sheet", "Dimensions")
    rows = [("Источник", "замеры сетки components/mg996r/mg996r.FCStd, 2026-11-02"),
            ("Система координат", "как у сетки: X ширина, Y высота, Z длина; вал вдоль Y через x=9.5, z=37.0"),
            ("Корпус", "x 0..19, z 7..47, y 0..35, снизу скос 1.1 мм до y=3"),
            ("Уши", "y 26.5..29, z 0..54, отверстия d4, шаг 49.5 x 10 (в сетке открытые пазы)"),
            ("Крышка и площадка", "y 35..37.25 (z 10.5..46.5), площадка до y 37.5, без углублений"),
            ("Бобышка и вал", "d13 до y 38.5, d11 до 39.5, d5 до 40.5, шлиц d5.6 до 43.5, отверстие d3"),
            ("Кабель", "d3 по z от 47 до 54.5, x 9.5, y 8.5"),
            ("Не моделируется", "рёбра на ушах 1 мм, штырёк 3x4, кольцо вокруг кабеля, углубления крышки"),
            ("Построение", "scripts/build-mg996r-brep.FCMacro")]
    for i, (k, v) in enumerate(rows, 1):
        sheet.set("A%d" % i, k)
        sheet.set("B%d" % i, v)
    doc.recompute()
    doc.saveAs(path)
    return path, round(shape.Volume, 1), shape.isValid(), len(shape.Solids), shape.BoundBox
